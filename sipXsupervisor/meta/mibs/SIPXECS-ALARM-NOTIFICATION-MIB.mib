--
-- Name:     sipXecs alarm notification MIB
-- Purpose:  To define the alarm notifications generated by sipXecs
-- File:     SIPXECS-ALARM-NOTIFICATION-MIB.mib
-- OID:      1.3.6.1.4.1.7142.100
-- Created:  04 November 2009
-- Revision: 1.0
-- Author:   Goutham B G
--
-- Copyright (c) 2010 Avaya
--
-- Revision History:
-- 04 Nov 2009          0.1    Initial Draft
-- 26 Nov 2009          0.2    Removed suggested resolution from the alarm attributes
-- 10 Feb 2010          1.0    Updated the description of severity with all possible levels.

SIPXECS-ALARM-NOTIFICATION-MIB DEFINITIONS ::= BEGIN

-- Imports

IMPORTS

    MODULE-IDENTITY, OBJECT-TYPE, enterprises,
    NOTIFICATION-TYPE                       FROM SNMPv2-SMI
    SnmpAdminString                         FROM SNMP-FRAMEWORK-MIB
;

--
-- sipXecs MIB
--

-- Pingtel enterprise identifier

  pingtel              OBJECT IDENTIFIER ::= { enterprises 7142 } -- .1.3.6.1.4.1.7142

-- sipXecs product branch (root node)

  sipxecs              OBJECT IDENTIFIER ::= { pingtel 100 }

-- sipXecs sub-branches (1st level nodes)

-- Alarms generated by sipXecs

  alarms               OBJECT IDENTIFIER ::= { sipxecs 1 } -- .1.3.6.1.4.1.7142.100.1


  alarmNotifications                OBJECT IDENTIFIER
                                    ::= { alarms 0 } -- .1.3.6.1.4.1.7142.100.1.0

  alarmAttributes                   OBJECT IDENTIFIER
                                    ::= { alarms 1 } -- .1.3.6.1.4.1.7142.100.1.1

-- Alarm attributes

sipxecsAlarmId OBJECT-TYPE
    SYNTAX      SnmpAdminString
    MAX-ACCESS  accessible-for-notify
    STATUS      current
    DESCRIPTION
        "A simple string that uniquely identifies an alarm."
    ::= { alarmAttributes 1 }

sipxecsAlarmSource OBJECT-TYPE
    SYNTAX      SnmpAdminString
    MAX-ACCESS  accessible-for-notify
    STATUS      current
    DESCRIPTION
        "The host that generated the alarm."
    ::= { alarmAttributes 2 }

sipxecsAlarmTime OBJECT-TYPE
    SYNTAX      OCTET STRING
    MAX-ACCESS  accessible-for-notify
    STATUS      current
    DESCRIPTION
        "The time the alarm was generated. The time is always in Universal Time."
    ::= { alarmAttributes 3 }

sipxecsAlarmSeverity OBJECT-TYPE
    SYNTAX      OCTET STRING
    MAX-ACCESS  accessible-for-notify
    STATUS      current
    DESCRIPTION
        "The Severity of the Alarm. The severity is one of debug, info, notice, warning, error, crit, alert, emerg."
    ::= { alarmAttributes 4 }

sipxecsAlarmDescr OBJECT-TYPE
    SYNTAX      OCTET STRING
    MAX-ACCESS  accessible-for-notify
    STATUS      current
    DESCRIPTION
        "A textual description of the alarm."
    ::= { alarmAttributes 5 }

-- Alarm notifications generated by sipXecs is defined in the below node.

sipxecsAlarmNotification NOTIFICATION-TYPE
    OBJECTS     { sipxecsAlarmId,
                  sipxecsAlarmSource,
                  sipxecsAlarmTime,
                  sipxecsAlarmSeverity,
                  sipxecsAlarmDescr }
    STATUS      current
    DESCRIPTION
        "Notification of the alarm generated by sipxecs. The attributes of this alarm are Alarm code,
         the host that generated the alarm, time the alarm was generated, alarm severity and description
         of the alarm."
    ::= { alarmNotifications 0 } -- .1.3.6.1.4.1.7142.100.1.0.0

END
